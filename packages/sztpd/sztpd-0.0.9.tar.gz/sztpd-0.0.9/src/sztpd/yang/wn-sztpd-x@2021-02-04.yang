module wn-sztpd-x {
  yang-version 1.1;
  namespace "https://watsen.net/sztpd-x";
  prefix sztpd-x;

  import wn-app {
    prefix wnapp;
    reference
      "https://watsen.net/products/common";
  }
  import wn-sztpd-rpcs {
    prefix sztpd-rpcs;
    reference
      "https://watsen.net/products/sztpd";
  }
  import wn-sztpd-0 {
    prefix sztpd-0;
    reference
      "https://watsen.net/products/szptd";
  }
  import wn-sztpd-1 {
    prefix sztpd-1;
    reference
      "https://watsen.net/products/szptd";
  }

  organization
    "Watsen Networks (https://watsen.net)";
  description
    "This module defines the data model for a bootstrap server
     for multi-tenant use.

     Copyright (c) 2021 Watsen Networks.  All Rights Reserved.";

  revision 2021-02-04 {
    description
      "Initial version";
  }

  feature device-ownership-verification {
    description
      "Indicates that device ownership verification is implemented
       at the multi-tenant level (not at the per-tenant level).";
  }

  uses sztpd-0:device-types-grouping;
  uses wnapp:multi-tenant-app-grouping {
    augment "preferences/outbound-interactions" {
      leaf relay-progress-report-callout {
        type leafref {
          path "../../../dynamic-callouts/dynamic-callout/name";
        }
      }
    }
    augment "preferences/system/features" {
      uses sztpd-0:prefs-system-features-grouping;
    }
    refine "transport/listen" {
      must 'endpoint/use-for = "native-interface"' {
        error-message "There must be at least one endpoint presenting the native API.";
      }
    }
    augment "transport/listen/endpoint" {
      description
        "Augments in an enumeration for the interface the RESTCONF
         server instance supports.

         While there must be exactly one 'native' interface, there
         may be any number of 'tenant' and 'rfc8572' interfaces.";
      leaf use-for {
        mandatory true;
        type enumeration {
          enum native-interface;
          enum tenant-interface;
          enum rfc8572-interface;
        }
      }
    }
    augment "tenants/tenant" {
      uses sztpd-1:generic-tenant-with-devices-grouping {
        augment "devices/device" {
          leaf device-type {
            type leafref {
              path "/device-types/device-type/name";
            }
            mandatory true;
            description
              "The type of device this device is.";
          }
        }
      }
    }
    augment "tenants/tenant/preferences/outbound-interactions" {
      leaf relay-progress-report-callout {
        type leafref {
          path "../../../dynamic-callouts/dynamic-callout/name";
        }
      }
    }
    augment "tenants/tenant/preferences/storage-management" {
      if-feature "wnapp:storage-reclamation-implemented";
      uses sztpd-0:prefs-storage-management-grouping;
    }
  }
}
